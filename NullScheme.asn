RPKINullScheme2025
  { iso(1) member-body(2) us(840) rsadsi(113549)
    pkcs(1) pkcs-9(9) smime(16) modules(0) null-scheme-2025(TBD) }
--
-- TODO: module ID to be replaced by IANA
--

DEFINITIONS IMPLICIT TAGS ::= BEGIN

EXPORTS ALL;

IMPORTS
  PUBLIC-KEY, SIGNATURE-ALGORITHM
    FROM AlgorithmInformation-2009  -- RFC 5912
      { iso(1) i id-mod(0)
        id-mod-algorithmInformation-02(58) }
;

--
-- TODO: OIDs to be replaced by IANA
--
id-RPKI-NULL-SCHEME OBJECT IDENTIFIER ::= {
    identified-organization(3) dod(6) internet(1)
        security(5) mechanisms(5) pkix(7) alg(6) TBD
  }

pk-RPKI-NULL-SCHEME PUBLIC-KEY ::= {
    IDENTIFIER id-RPKI-NULL-SCHEME
    -- The digest algorithm used to determine the input to the signing / verification
    -- algorithms is determined by the SignerInfo's digestAlgorithm field. The signing
    -- and verification algorithms themselves are not dependent on the digest algorithm,
    -- so we don't need PARAMS or distinct OIDs for pairing different digest algorithms.
    PARAMS ARE absent
    -- A Null Scheme public key should only be certified by EE certificates.
    -- So, in accordance with RFC6487, only the digitalSignature bit is valid.
    CERT-KEY-USAGE {digitalSignature} 
  }

sa-RPKI-NULL-SCHEME SIGNATURE-ALGORITHM ::= {
    IDENTIFIER id-RPKI-NULL-SCHEME
    PARAMS ARE absent
    PUBLIC-KEYS {pk-RPKI-NULL-SCHEME}
  }

END
